[DOCUMENT]
TITLE: Step2 Index
UID: GENERATED-55b769cb
[REQUIREMENT]
MID: 36faf9ad546c4250
TITLE: Step2 Index
STATEMENT: >>>

<<<
[/REQUIREMENT]
[REQUIREMENT]
MID: 62ab033ad2af4926
TITLE: Requirements Documentation Index
STATEMENT: >>>

Total files processed: 5

## Requirements Documents by Subdirectory

### administration.ui

- [administration.ui/src/main/java/at/a1ta/cuco/admin/ui/common/server/CCTOrgStructureElementUploadServlet.java](./administration.ui/CCTOrgStructureElementUploadServlet.md)

### cuco-cct-core

- [cuco-cct-core/src/test/java/at/a1ta/cuco/cct/productoffering/bfw1/v1/shared/BFWV1DefaultConfigurationTest.java](./cuco-cct-core/BFWV1DefaultConfigurationTest.md)
- [cuco-cct-core/src/test/java/at/a1ta/cuco/cct/productoffering/marketplace/v1/shared/MarketplaceProductGenerator.java](./cuco-cct-core/MarketplaceProductGenerator.md)
- [cuco-cct-core/src/test/java/at/a1ta/cuco/cct/productoffering/marketplace/v1/shared/MarketplaceV1DefaultConfigurationTest.java](./cuco-cct-core/MarketplaceV1DefaultConfigurationTest.md)
- [cuco-cct-core/src/test/java/at/a1ta/cuco/cct/util/ReflectionUtilTest.java](./cuco-cct-core/ReflectionUtilTest.md)


<<<
[/REQUIREMENT]
[/DOCUMENT]
