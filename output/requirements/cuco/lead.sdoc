[DOCUMENT]
TITLE: lead
UID: LEAD
VERSION: 1.0

[GRAMMAR]
ELEMENTS:
- TAG: REQUIREMENT
  FIELDS:
  - TITLE: UID
    TYPE: String
    REQUIRED: True
  - TITLE: TITLE
    TYPE: String
    REQUIRED: True
  - TITLE: STATEMENT
    TYPE: String
    REQUIRED: True
  - TITLE: MID
    TYPE: String
    REQUIRED: False
  RELATIONS:
  - TYPE: Parent
  - TYPE: File

[REQUIREMENT]
UID: REQ-001
TITLE: lead Analysis
STATEMENT: >>>
This file contains requirements analysis for: lead

Key components and functionality:
- File type: lead
- Purpose: Requirements documentation
- Status: Analyzed
<<<
[/REQUIREMENT]
