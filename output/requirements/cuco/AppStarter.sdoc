[DOCUMENT]
TITLE: AppStarter
UID: APPSTARTER
VERSION: 1.0

[GRAMMAR]
ELEMENTS:
- TAG: REQUIREMENT
  FIELDS:
  - TITLE: UID
    TYPE: String
    REQUIRED: True
  - TITLE: TITLE
    TYPE: String
    REQUIRED: True
  - TITLE: STATEMENT
    TYPE: String
    REQUIRED: True
  - TITLE: MID
    TYPE: String
    REQUIRED: False
  RELATIONS:
  - TYPE: Parent
  - TYPE: File

[REQUIREMENT]
UID: REQ-001
TITLE: AppStarter Analysis
STATEMENT: >>>
This file contains requirements analysis for: AppStarter

Key components and functionality:
- File type: AppStarter
- Purpose: Requirements documentation
- Status: Analyzed
<<<
[/REQUIREMENT]
