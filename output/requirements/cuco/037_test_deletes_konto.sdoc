[DOCUMENT]
TITLE: 037_test_deletes_konto
UID: 037_TEST_DELETES_KONTO
VERSION: 1.0

[GRAMMAR]
ELEMENTS:
- TAG: REQUIREMENT
  FIELDS:
  - TITLE: UID
    TYPE: String
    REQUIRED: True
  - TITLE: TITLE
    TYPE: String
    REQUIRED: True
  - TITLE: STATEMENT
    TYPE: String
    REQUIRED: True
  - TITLE: MID
    TYPE: String
    REQUIRED: False
  RELATIONS:
  - TYPE: Parent
  - TYPE: File

[REQUIREMENT]
UID: REQ-001
TITLE: 037_test_deletes_konto Analysis
STATEMENT: >>>
This file contains requirements analysis for: 037_test_deletes_konto

Key components and functionality:
- File type: 037_test_deletes_konto
- Purpose: Requirements documentation
- Status: Analyzed
<<<
[/REQUIREMENT]
