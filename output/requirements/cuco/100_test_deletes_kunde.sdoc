[DOCUMENT]
TITLE: 100_test_deletes_kunde
UID: 100_TEST_DELETES_KUNDE
VERSION: 1.0

[GRAMMAR]
ELEMENTS:
- TAG: REQUIREMENT
  FIELDS:
  - TITLE: UID
    TYPE: String
    REQUIRED: True
  - TITLE: TITLE
    TYPE: String
    REQUIRED: True
  - TITLE: STATEMENT
    TYPE: String
    REQUIRED: True
  - TITLE: MID
    TYPE: String
    REQUIRED: False
  RELATIONS:
  - TYPE: Parent
  - TYPE: File

[REQUIREMENT]
UID: REQ-001
TITLE: 100_test_deletes_kunde Analysis
STATEMENT: >>>
This file contains requirements analysis for: 100_test_deletes_kunde

Key components and functionality:
- File type: 100_test_deletes_kunde
- Purpose: Requirements documentation
- Status: Analyzed
<<<
[/REQUIREMENT]
