[DOCUMENT]
TITLE: 035_test_deletes_bestand
UID: 035_TEST_DELETES_BESTAND
VERSION: 1.0

[GRAMMAR]
ELEMENTS:
- TAG: REQUIREMENT
  FIELDS:
  - TITLE: UID
    TYPE: String
    REQUIRED: True
  - TITLE: TITLE
    TYPE: String
    REQUIRED: True
  - TITLE: STATEMENT
    TYPE: String
    REQUIRED: True
  - TITLE: MID
    TYPE: String
    REQUIRED: False
  RELATIONS:
  - TYPE: Parent
  - TYPE: File

[REQUIREMENT]
UID: REQ-001
TITLE: 035_test_deletes_bestand Analysis
STATEMENT: >>>
This file contains requirements analysis for: 035_test_deletes_bestand

Key components and functionality:
- File type: 035_test_deletes_bestand
- Purpose: Requirements documentation
- Status: Analyzed
<<<
[/REQUIREMENT]
