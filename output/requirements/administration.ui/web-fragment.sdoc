[DOCUMENT]
TITLE: web-fragment
UID: WEB_FRAGMENT
VERSION: 1.0

[GRAMMAR]
ELEMENTS:
- TAG: REQUIREMENT
  FIELDS:
  - TITLE: UID
    TYPE: String
    REQUIRED: True
  - TITLE: TITLE
    TYPE: String
    REQUIRED: True
  - TITLE: STATEMENT
    TYPE: String
    REQUIRED: True
  - TITLE: MID
    TYPE: String
    REQUIRED: False
  RELATIONS:
  - TYPE: Parent
  - TYPE: File

[REQUIREMENT]
UID: REQ-001
TITLE: web-fragment Analysis
STATEMENT: >>>
This file contains requirements analysis for: web-fragment

Key components and functionality:
- File type: web-fragment
- Purpose: Requirements documentation
- Status: Analyzed
<<<
[/REQUIREMENT]
