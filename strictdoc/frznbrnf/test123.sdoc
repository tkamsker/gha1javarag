[DOCUMENT]
TITLE: test123
UID: TEST123
VERSION: 1.0

[GRAMMAR]
ELEMENTS:
- TAG: REQUIREMENT
  FIELDS:
  - TITLE: UID
    TYPE: String
    REQUIRED: True
  - TITLE: TITLE
    TYPE: String
    REQUIRED: True
  - TITLE: STATEMENT
    TYPE: String
    REQUIRED: True
  - TITLE: MID
    TYPE: String
    REQUIRED: False
  RELATIONS:
  - TYPE: Parent
  - TYPE: File

[REQUIREMENT]
UID: REQ-001
TITLE: test123 Analysis
STATEMENT: >>>
This file contains requirements analysis for: test123

Key components and functionality:
- File type: test123
- Purpose: Requirements documentation
- Status: Analyzed
<<<
[/REQUIREMENT]
